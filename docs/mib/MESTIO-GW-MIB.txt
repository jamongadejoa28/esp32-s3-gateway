MESTIO-GW-MIB DEFINITIONS ::= BEGIN

-- Generated by tools/gen_mib.py from components/mex150/regmap.def and
-- components/alarm/alarm_catalog.def (enterprise 32473). Do not edit.

IMPORTS
    MODULE-IDENTITY, OBJECT-TYPE, NOTIFICATION-TYPE, enterprises,
    Integer32, Unsigned32, Counter32, Gauge32, TimeTicks
        FROM SNMPv2-SMI
    TEXTUAL-CONVENTION, DisplayString, TruthValue, DateAndTime, MacAddress
        FROM SNMPv2-TC
    MODULE-COMPLIANCE, OBJECT-GROUP, NOTIFICATION-GROUP
        FROM SNMPv2-CONF;

mestioGwMIB MODULE-IDENTITY
    LAST-UPDATED "202610190000Z"
    ORGANIZATION "MESTIO"
    CONTACT-INFO "MESTIO technical support"
    DESCRIPTION "Management information of the MESTIO Gateway, a Modbus RTU (RS485) to SNMP/HTTP
            gateway for MEX150 HVAC controllers. Device tables are indexed by gwDevIndex
            (configured device id + 1). SNMPv3 access uses USM authPriv with HMAC-SHA-96 and
            AES-128; read-only and read-write users are separate."
    REVISION     "202610190000Z"
    DESCRIPTION  "Initial version."
    ::= { enterprises 32473 1 }

-- ---------------------------------------------------------------- textual conventions

GwTenths ::= TEXTUAL-CONVENTION
    DISPLAY-HINT "d-1"
    STATUS       current
    DESCRIPTION  "An integer in tenths of the unit given by the object (235 means 23.5)."
    SYNTAX       Integer32

GwDevIndex ::= TEXTUAL-CONVENTION
    DISPLAY-HINT "d"
    STATUS       current
    DESCRIPTION  "Index of a configured Modbus device: device id + 1."
    SYNTAX       Integer32 (1..4)

GwUtf8String ::= TEXTUAL-CONVENTION
    DISPLAY-HINT "255t"
    STATUS       current
    DESCRIPTION  "Text in UTF-8 (RFC 3629), not NUL-terminated."
    SYNTAX       OCTET STRING (SIZE (0..255))

GwAlarmSeverity ::= TEXTUAL-CONVENTION
    STATUS       current
    DESCRIPTION  "Alarm severity."
    SYNTAX       INTEGER { info(1), minor(2), major(3), critical(4) }

GwWriteResult ::= TEXTUAL-CONVENTION
    STATUS       current
    DESCRIPTION  "Outcome of a register write: none(1) no write since boot, pending(2) queued and
                 not finished yet, applied(3) written and verified by reading back, rejected(4)
                 refused by the gateway or the device, uncertain(5) written but not verified."
    SYNTAX       INTEGER { none(1), pending(2), applied(3), rejected(4), uncertain(5) }

GwAlarmCode ::= TEXTUAL-CONVENTION
    STATUS       current
    DESCRIPTION  "Stable alarm code (never renumbered). 1xx: MEX150 alarm coils (100 + coil),
                 2xx: MEX150 register bits, 3xx: gateway-generated, 4xx: user threshold rules
                 (400 + rule id).

                 117 blowerFault: Blower fault (MEX150 coil 17; default severity major).
                 118 cool1Fault: Cooling 1 fault (MEX150 coil 18; default severity major).
                 119 cool2Fault: Cooling 2 fault (MEX150 coil 19; default severity major).
                 120 heaterFault: Heater fault (MEX150 coil 20; default severity major).
                 121 humidifierFault: Humidifier fault (MEX150 coil 21; default severity major).
                 122 sensorFault: Sensor fault (MEX150 coil 22; default severity major).
                 123 leak: Water leak (MEX150 coil 23; default severity critical).
                 124 supplyFault: Water supply fault (MEX150 coil 24; default severity minor).
                 125 drainFault: Drain fault (MEX150 coil 25; default severity minor).
                 126 lowTemp: Low temperature (MEX150 coil 26; default severity major).
                 127 highTemp: High temperature (MEX150 coil 27; default severity major).
                 128 lowHum: Low humidity (MEX150 coil 28; default severity minor).
                 129 highHum: High humidity (MEX150 coil 29; default severity minor).
                 130 fire: Fire (MEX150 coil 30; default severity critical).
                 131 cool3Fault: Cooling 3 fault (MEX150 coil 31; default severity major).
                 201 contamination: Cylinder contamination (register 40003 bit 7; default
                 severity minor).
                 301 commLost: Communication lost (gateway: device communication lost; default
                 severity major).
                 401 rule1: User rule 1 (user threshold rule 1; default severity major).
                 402 rule2: User rule 2 (user threshold rule 2; default severity major).
                 403 rule3: User rule 3 (user threshold rule 3; default severity major).
                 404 rule4: User rule 4 (user threshold rule 4; default severity major).
                 405 rule5: User rule 5 (user threshold rule 5; default severity major).
                 406 rule6: User rule 6 (user threshold rule 6; default severity major).
                 407 rule7: User rule 7 (user threshold rule 7; default severity major).
                 408 rule8: User rule 8 (user threshold rule 8; default severity major)."
    SYNTAX       INTEGER {
                     blowerFault(117),
                     cool1Fault(118),
                     cool2Fault(119),
                     heaterFault(120),
                     humidifierFault(121),
                     sensorFault(122),
                     leak(123),
                     supplyFault(124),
                     drainFault(125),
                     lowTemp(126),
                     highTemp(127),
                     lowHum(128),
                     highHum(129),
                     fire(130),
                     cool3Fault(131),
                     contamination(201),
                     commLost(301),
                     rule1(401),
                     rule2(402),
                     rule3(403),
                     rule4(404),
                     rule5(405),
                     rule6(406),
                     rule7(407),
                     rule8(408)
                 }

-- ---------------------------------------------------------------- branches

gwNotifications OBJECT IDENTIFIER ::= { mestioGwMIB 0 }
gwInfo          OBJECT IDENTIFIER ::= { mestioGwMIB 1 }
gwDevices       OBJECT IDENTIFIER ::= { mestioGwMIB 2 }
mexStatus       OBJECT IDENTIFIER ::= { mestioGwMIB 3 }
mexSetpoints    OBJECT IDENTIFIER ::= { mestioGwMIB 4 }
mexRegisters    OBJECT IDENTIFIER ::= { mestioGwMIB 5 }
gwAlarms        OBJECT IDENTIFIER ::= { mestioGwMIB 6 }
gwComm          OBJECT IDENTIFIER ::= { mestioGwMIB 7 }
gwConformance   OBJECT IDENTIFIER ::= { mestioGwMIB 8 }

-- ---------------------------------------------------------------- gwInfo (also sysObjectID)

gwFwVersion OBJECT-TYPE
    SYNTAX      DisplayString (SIZE (0..31))
    MAX-ACCESS  read-only
    STATUS      current
    DESCRIPTION "Firmware version of the gateway (application image version)."
    ::= { gwInfo 1 }

gwMacAddress OBJECT-TYPE
    SYNTAX      MacAddress
    MAX-ACCESS  read-only
    STATUS      current
    DESCRIPTION "Base MAC address of the gateway (eFuse); the hostname, SSID and SNMP engine ID
            derive from it."
    ::= { gwInfo 2 }

gwUptime OBJECT-TYPE
    SYNTAX      TimeTicks
    MAX-ACCESS  read-only
    STATUS      current
    DESCRIPTION "Time since the gateway booted (same clock as sysUpTime)."
    ::= { gwInfo 3 }

gwTimeValid OBJECT-TYPE
    SYNTAX      TruthValue
    MAX-ACCESS  read-only
    STATUS      current
    DESCRIPTION "true(1) once the wall clock has been set (RTC, NTP or a user); otherwise every
            DateAndTime of this MIB reads 1970-01-01."
    ::= { gwInfo 4 }

gwWallTime OBJECT-TYPE
    SYNTAX      DateAndTime
    MAX-ACCESS  read-only
    STATUS      current
    DESCRIPTION "Current wall clock time (UTC)."
    ::= { gwInfo 5 }

gwActiveAlarms OBJECT-TYPE
    SYNTAX      Gauge32
    MAX-ACCESS  read-only
    STATUS      current
    DESCRIPTION "Number of active alarms over all devices."
    ::= { gwInfo 6 }

gwConfigRev OBJECT-TYPE
    SYNTAX      Unsigned32
    MAX-ACCESS  read-only
    STATUS      current
    DESCRIPTION "Configuration revision; incremented by every committed configuration change."
    ::= { gwInfo 7 }

gwLastConfigSection OBJECT-TYPE
    SYNTAX      DisplayString (SIZE (0..16))
    MAX-ACCESS  read-only
    STATUS      current
    DESCRIPTION "Name of the configuration section changed last (general, network, modbus, alarms,
            snmp, time, security, notify or secrets); empty until the first change since boot."
    ::= { gwInfo 8 }

gwLastWriteResult OBJECT-TYPE
    SYNTAX      GwWriteResult
    MAX-ACCESS  read-only
    STATUS      current
    DESCRIPTION "Outcome of the most recent register write request from any origin (web, SNMP,
            console). A SET of mexSetpointTable that the device did not verify answers noError
            and is reported here as uncertain(5) or pending(2)."
    ::= { gwInfo 9 }

gwLastWriteDevIndex OBJECT-TYPE
    SYNTAX      Integer32 (0..4)
    MAX-ACCESS  read-only
    STATUS      current
    DESCRIPTION "Device index of the most recent write request; 0 when there was none."
    ::= { gwInfo 10 }

gwLastWriteRegAddr OBJECT-TYPE
    SYNTAX      Integer32 (0..65535)
    MAX-ACCESS  read-only
    STATUS      current
    DESCRIPTION "Register address (4xxxx) of the most recent write request; 0 when there was none."
    ::= { gwInfo 11 }

gwLastWriteValue OBJECT-TYPE
    SYNTAX      Integer32
    MAX-ACCESS  read-only
    STATUS      current
    DESCRIPTION "Requested raw value (register scale) of the most recent write request."
    ::= { gwInfo 12 }

gwLastWriteReason OBJECT-TYPE
    SYNTAX      DisplayString (SIZE (0..32))
    MAX-ACCESS  read-only
    STATUS      current
    DESCRIPTION "Reason of a rejected or uncertain write (for example range, running_interlock,
            offline, exception:2, verify_mismatch); empty when applied."
    ::= { gwInfo 13 }

gwLastWriteTime OBJECT-TYPE
    SYNTAX      DateAndTime
    MAX-ACCESS  read-only
    STATUS      current
    DESCRIPTION "Time of the most recent write result."
    ::= { gwInfo 14 }

gwLastWriteCommand OBJECT-TYPE
    SYNTAX      Unsigned32
    MAX-ACCESS  read-only
    STATUS      current
    DESCRIPTION "Command identifier of the most recent write (0 when it was rejected before
            queueing)."
    ::= { gwInfo 15 }

gwLastWritePrincipal OBJECT-TYPE
    SYNTAX      GwUtf8String (SIZE (0..11))
    MAX-ACCESS  read-only
    STATUS      current
    DESCRIPTION "Who requested the most recent write: @snmp, @console, or for a web user the account
            name (SNMPv3 requests only; SNMPv1/v2c requests read web)."
    ::= { gwInfo 16 }

gwTrapsSent OBJECT-TYPE
    SYNTAX      Counter32
    MAX-ACCESS  read-only
    STATUS      current
    DESCRIPTION "Notifications sent (trap or inform datagrams)."
    ::= { gwInfo 17 }

gwTrapsDropped OBJECT-TYPE
    SYNTAX      Counter32
    MAX-ACCESS  read-only
    STATUS      current
    DESCRIPTION "Notifications not sent because of the rate limit (10 per second) or a full queue."
    ::= { gwInfo 18 }

gwInformsFailed OBJECT-TYPE
    SYNTAX      Counter32
    MAX-ACCESS  read-only
    STATUS      current
    DESCRIPTION "Inform requests that were not acknowledged after all retransmissions."
    ::= { gwInfo 19 }

-- ---------------------------------------------------------------- gwDevices

gwDevTable OBJECT-TYPE
    SYNTAX      SEQUENCE OF GwDevEntry
    MAX-ACCESS  not-accessible
    STATUS      current
    DESCRIPTION "Configured Modbus devices."
    ::= { gwDevices 1 }

gwDevEntry OBJECT-TYPE
    SYNTAX      GwDevEntry
    MAX-ACCESS  not-accessible
    STATUS      current
    DESCRIPTION "One configured device."
    INDEX       { gwDevIndex }
    ::= { gwDevTable 1 }

GwDevEntry ::= SEQUENCE {
    gwDevIndex   GwDevIndex,
    gwDevName    GwUtf8String,
    gwDevSlave   Integer32,
    gwDevEnabled TruthValue,
    gwDevOnline  TruthValue,
    gwDevDataAge Unsigned32,
    gwDevSeq     Counter32
}

gwDevIndex OBJECT-TYPE
    SYNTAX      GwDevIndex
    MAX-ACCESS  not-accessible
    STATUS      current
    DESCRIPTION "Device index (configured Modbus device id + 1)."
    ::= { gwDevEntry 1 }

gwDevName OBJECT-TYPE
    SYNTAX      GwUtf8String (SIZE (0..23))
    MAX-ACCESS  read-only
    STATUS      current
    DESCRIPTION "Configured device name."
    ::= { gwDevEntry 2 }

gwDevSlave OBJECT-TYPE
    SYNTAX      Integer32 (1..247)
    MAX-ACCESS  read-only
    STATUS      current
    DESCRIPTION "Modbus unit address of the device."
    ::= { gwDevEntry 3 }

gwDevEnabled OBJECT-TYPE
    SYNTAX      TruthValue
    MAX-ACCESS  read-only
    STATUS      current
    DESCRIPTION "true(1) if the device is polled."
    ::= { gwDevEntry 4 }

gwDevOnline OBJECT-TYPE
    SYNTAX      TruthValue
    MAX-ACCESS  read-only
    STATUS      current
    DESCRIPTION "true(1) while the device answers polls."
    ::= { gwDevEntry 5 }

gwDevDataAge OBJECT-TYPE
    SYNTAX      Unsigned32
    UNITS       "milliseconds"
    MAX-ACCESS  read-only
    STATUS      current
    DESCRIPTION "Age of the last successful poll cycle; 4294967295 if the device was never polled."
    ::= { gwDevEntry 6 }

gwDevSeq OBJECT-TYPE
    SYNTAX      Counter32
    MAX-ACCESS  read-only
    STATUS      current
    DESCRIPTION "Number of successful poll cycles (snapshot sequence)."
    ::= { gwDevEntry 7 }

gwDevCount OBJECT-TYPE
    SYNTAX      Integer32 (0..4)
    MAX-ACCESS  read-only
    STATUS      current
    DESCRIPTION "Number of configured devices (rows of gwDevTable)."
    ::= { gwDevices 2 }

-- ---------------------------------------------------------------- mexStatus

mexStatusTable OBJECT-TYPE
    SYNTAX      SEQUENCE OF MexStatusEntry
    MAX-ACCESS  not-accessible
    STATUS      current
    DESCRIPTION "Live status of each configured MEX150."
    ::= { mexStatus 1 }

mexStatusEntry OBJECT-TYPE
    SYNTAX      MexStatusEntry
    MAX-ACCESS  not-accessible
    STATUS      current
    DESCRIPTION "Status of one device."
    INDEX       { gwDevIndex }
    ::= { mexStatusTable 1 }

MexStatusEntry ::= SEQUENCE {
    mexStatusValid    TruthValue,
    mexTemperature    GwTenths,
    mexHumidity       GwTenths,
    mexCurrent        GwTenths,
    mexRunState       INTEGER,
    mexDelayRemaining Integer32,
    mexModeFlags      BITS,
    mexStagesCool     Unsigned32,
    mexStagesHeat     Unsigned32,
    mexStagesHum      Unsigned32,
    mexStagesDehum    Unsigned32,
    mexBlower         TruthValue,
    mexCoils          Unsigned32,
    mexInputPort      Unsigned32,
    mexAlarmDetail1   Unsigned32,
    mexAlarmDetail2   Unsigned32,
    mexCoolProp       Unsigned32,
    mexHeatProp       Unsigned32,
    mexHumProp        Unsigned32
}

mexStatusValid OBJECT-TYPE
    SYNTAX      TruthValue
    MAX-ACCESS  read-only
    STATUS      current
    DESCRIPTION "true(1) if the device is online and its data is fresh (younger than 3 seconds);
            otherwise the other columns show the last known values."
    ::= { mexStatusEntry 1 }

mexTemperature OBJECT-TYPE
    SYNTAX      GwTenths
    UNITS       "degrees Celsius"
    MAX-ACCESS  read-only
    STATUS      current
    DESCRIPTION "Current temperature (register 40036)."
    ::= { mexStatusEntry 2 }

mexHumidity OBJECT-TYPE
    SYNTAX      GwTenths
    UNITS       "percent"
    MAX-ACCESS  read-only
    STATUS      current
    DESCRIPTION "Current relative humidity (register 40037)."
    ::= { mexStatusEntry 3 }

mexCurrent OBJECT-TYPE
    SYNTAX      GwTenths
    UNITS       "amperes"
    MAX-ACCESS  read-only
    STATUS      current
    DESCRIPTION "Current consumption (register 40011)."
    ::= { mexStatusEntry 4 }

mexRunState OBJECT-TYPE
    SYNTAX      INTEGER { stopped(1), running(2) }
    MAX-ACCESS  read-only
    STATUS      current
    DESCRIPTION "Run state of the unit (register 40005, low byte)."
    ::= { mexStatusEntry 5 }

mexDelayRemaining OBJECT-TYPE
    SYNTAX      Integer32 (0..255)
    UNITS       "seconds"
    MAX-ACCESS  read-only
    STATUS      current
    DESCRIPTION "Remaining run/stop delay (register 40005, high byte)."
    ::= { mexStatusEntry 6 }

mexModeFlags OBJECT-TYPE
    SYNTAX      BITS { cooling(0), heating(1), humidifying(2), dehumidifying(3) }
    MAX-ACCESS  read-only
    STATUS      current
    DESCRIPTION "Active operating modes (coils 12 to 15)."
    ::= { mexStatusEntry 7 }

mexStagesCool OBJECT-TYPE
    SYNTAX      Unsigned32 (0..3)
    MAX-ACCESS  read-only
    STATUS      current
    DESCRIPTION "Running cooling stages (coils 2, 3 and 16)."
    ::= { mexStatusEntry 8 }

mexStagesHeat OBJECT-TYPE
    SYNTAX      Unsigned32 (0..4)
    MAX-ACCESS  read-only
    STATUS      current
    DESCRIPTION "Running heating stages (coils 4 to 7)."
    ::= { mexStatusEntry 9 }

mexStagesHum OBJECT-TYPE
    SYNTAX      Unsigned32 (0..2)
    MAX-ACCESS  read-only
    STATUS      current
    DESCRIPTION "Running humidifier stages (coils 8 and 9)."
    ::= { mexStatusEntry 10 }

mexStagesDehum OBJECT-TYPE
    SYNTAX      Unsigned32 (0..1)
    MAX-ACCESS  read-only
    STATUS      current
    DESCRIPTION "Dehumidifying active (coil 15)."
    ::= { mexStatusEntry 11 }

mexBlower OBJECT-TYPE
    SYNTAX      TruthValue
    MAX-ACCESS  read-only
    STATUS      current
    DESCRIPTION "Blower running (coil 1)."
    ::= { mexStatusEntry 12 }

mexCoils OBJECT-TYPE
    SYNTAX      Unsigned32
    MAX-ACCESS  read-only
    STATUS      current
    DESCRIPTION "All 32 coils as a bit map: bit n-1 (value 2^(n-1)) is coil n. Coils 1 to 16 are run
            states, coils 17 to 31 alarms, coil 32 the combined alarm."
    ::= { mexStatusEntry 13 }

mexInputPort OBJECT-TYPE
    SYNTAX      Unsigned32 (0..65535)
    MAX-ACCESS  read-only
    STATUS      current
    DESCRIPTION "Input port bits (register 40002)."
    ::= { mexStatusEntry 14 }

mexAlarmDetail1 OBJECT-TYPE
    SYNTAX      Unsigned32 (0..65535)
    MAX-ACCESS  read-only
    STATUS      current
    DESCRIPTION "Alarm detail 1 bits (register 40003)."
    ::= { mexStatusEntry 15 }

mexAlarmDetail2 OBJECT-TYPE
    SYNTAX      Unsigned32 (0..65535)
    MAX-ACCESS  read-only
    STATUS      current
    DESCRIPTION "Alarm detail 2 bits (register 40004)."
    ::= { mexStatusEntry 16 }

mexCoolProp OBJECT-TYPE
    SYNTAX      Unsigned32 (0..65535)
    MAX-ACCESS  read-only
    STATUS      current
    DESCRIPTION "Cooling proportional bits (register 40006)."
    ::= { mexStatusEntry 17 }

mexHeatProp OBJECT-TYPE
    SYNTAX      Unsigned32 (0..65535)
    MAX-ACCESS  read-only
    STATUS      current
    DESCRIPTION "Heating proportional bits (register 40007)."
    ::= { mexStatusEntry 18 }

mexHumProp OBJECT-TYPE
    SYNTAX      Unsigned32 (0..65535)
    MAX-ACCESS  read-only
    STATUS      current
    DESCRIPTION "Humidifying proportional bits (register 40008)."
    ::= { mexStatusEntry 19 }

-- ---------------------------------------------------------------- mexSetpoints

mexSetpointTable OBJECT-TYPE
    SYNTAX      SEQUENCE OF MexSetpointEntry
    MAX-ACCESS  not-accessible
    STATUS      current
    DESCRIPTION "Writable set points of each configured MEX150. Column numbers are the register
            address minus 40000. Write access requires the read-write community (SNMPv1/v2c) or
            a read-write SNMPv3 user."
    ::= { mexSetpoints 1 }

mexSetpointEntry OBJECT-TYPE
    SYNTAX      MexSetpointEntry
    MAX-ACCESS  not-accessible
    STATUS      current
    DESCRIPTION "Set points of one device."
    INDEX       { gwDevIndex }
    ::= { mexSetpointTable 1 }

MexSetpointEntry ::= SEQUENCE {
    mexSpSetTemp   GwTenths,
    mexSpSetHum    GwTenths,
    mexSpCoolDev   GwTenths,
    mexSpHeatDev   GwTenths,
    mexSpHumDev    GwTenths,
    mexSpDehumDev  GwTenths,
    mexSpRunDelay  Integer32,
    mexSpStopDelay Integer32,
    mexSpHiTemp    GwTenths,
    mexSpLoTemp    GwTenths,
    mexSpHiHum     GwTenths,
    mexSpLoHum     GwTenths
}

mexSpSetTemp OBJECT-TYPE
    SYNTAX      GwTenths (50..500)
    UNITS       "degrees Celsius"
    MAX-ACCESS  read-write
    STATUS      current
    DESCRIPTION "Temperature setpoint (register 40012, key set_temp). Raw value in tenths of a unit;
            valid range 50 to 500. A SET is checked like a web write (device online with fresh
            data, range, run interlock) and then written to the device and read back: a
            rejection by the gateway or the device answers an error (commitFailed for a single
            varbind), an unverified write answers noError and is reported in gwLastWriteResult."
    ::= { mexSetpointEntry 12 }

mexSpSetHum OBJECT-TYPE
    SYNTAX      GwTenths (200..800)
    UNITS       "percent"
    MAX-ACCESS  read-write
    STATUS      current
    DESCRIPTION "Humidity setpoint (register 40013, key set_hum). Raw value in tenths of a unit;
            valid range 200 to 800. A SET is checked like a web write (device online with fresh
            data, range, run interlock) and then written to the device and read back: a
            rejection by the gateway or the device answers an error (commitFailed for a single
            varbind), an unverified write answers noError and is reported in gwLastWriteResult."
    ::= { mexSetpointEntry 13 }

mexSpCoolDev OBJECT-TYPE
    SYNTAX      GwTenths (1..100)
    UNITS       "degrees Celsius"
    MAX-ACCESS  read-write
    STATUS      current
    DESCRIPTION "Cooling deviation (register 40014, key cool_dev). Raw value in tenths of a unit;
            valid range 1 to 100. A SET is checked like a web write (device online with fresh
            data, range, run interlock) and then written to the device and read back: a
            rejection by the gateway or the device answers an error (commitFailed for a single
            varbind), an unverified write answers noError and is reported in gwLastWriteResult."
    ::= { mexSetpointEntry 14 }

mexSpHeatDev OBJECT-TYPE
    SYNTAX      GwTenths (1..100)
    UNITS       "degrees Celsius"
    MAX-ACCESS  read-write
    STATUS      current
    DESCRIPTION "Heating deviation (register 40015, key heat_dev). Raw value in tenths of a unit;
            valid range 1 to 100. A SET is checked like a web write (device online with fresh
            data, range, run interlock) and then written to the device and read back: a
            rejection by the gateway or the device answers an error (commitFailed for a single
            varbind), an unverified write answers noError and is reported in gwLastWriteResult."
    ::= { mexSetpointEntry 15 }

mexSpHumDev OBJECT-TYPE
    SYNTAX      GwTenths (10..100)
    UNITS       "percent"
    MAX-ACCESS  read-write
    STATUS      current
    DESCRIPTION "Humidifying deviation (register 40016, key hum_dev). Raw value in tenths of a unit;
            valid range 10 to 100. A SET is checked like a web write (device online with fresh
            data, range, run interlock) and then written to the device and read back: a
            rejection by the gateway or the device answers an error (commitFailed for a single
            varbind), an unverified write answers noError and is reported in gwLastWriteResult."
    ::= { mexSetpointEntry 16 }

mexSpDehumDev OBJECT-TYPE
    SYNTAX      GwTenths (10..100)
    UNITS       "percent"
    MAX-ACCESS  read-write
    STATUS      current
    DESCRIPTION "Dehumidifying deviation (register 40017, key dehum_dev). Raw value in tenths of a
            unit; valid range 10 to 100. A SET is checked like a web write (device online with
            fresh data, range, run interlock) and then written to the device and read back: a
            rejection by the gateway or the device answers an error (commitFailed for a single
            varbind), an unverified write answers noError and is reported in gwLastWriteResult."
    ::= { mexSetpointEntry 17 }

mexSpRunDelay OBJECT-TYPE
    SYNTAX      Integer32 (1..180)
    UNITS       "seconds"
    MAX-ACCESS  read-write
    STATUS      current
    DESCRIPTION "Run delay (register 40018, key run_delay). Raw value in units; valid range 1 to 180.
            A SET is checked like a web write (device online with fresh data, range, run
            interlock) and then written to the device and read back: a rejection by the gateway
            or the device answers an error (commitFailed for a single varbind), an unverified
            write answers noError and is reported in gwLastWriteResult."
    ::= { mexSetpointEntry 18 }

mexSpStopDelay OBJECT-TYPE
    SYNTAX      Integer32 (1..180)
    UNITS       "seconds"
    MAX-ACCESS  read-write
    STATUS      current
    DESCRIPTION "Stop delay (register 40019, key stop_delay). Raw value in units; valid range 1 to
            180. A SET is checked like a web write (device online with fresh data, range, run
            interlock) and then written to the device and read back: a rejection by the gateway
            or the device answers an error (commitFailed for a single varbind), an unverified
            write answers noError and is reported in gwLastWriteResult."
    ::= { mexSetpointEntry 19 }

mexSpHiTemp OBJECT-TYPE
    SYNTAX      GwTenths (249..500)
    UNITS       "degrees Celsius"
    MAX-ACCESS  read-write
    STATUS      current
    DESCRIPTION "High temperature limit (register 40027, key hi_temp). Raw value in tenths of a unit;
            valid range 250 to 500. The raw value 249 switches the function off. Writable only
            while the unit is stopped. A SET is checked like a web write (device online with
            fresh data, range, run interlock) and then written to the device and read back: a
            rejection by the gateway or the device answers an error (commitFailed for a single
            varbind), an unverified write answers noError and is reported in gwLastWriteResult."
    ::= { mexSetpointEntry 27 }

mexSpLoTemp OBJECT-TYPE
    SYNTAX      GwTenths (49..200)
    UNITS       "degrees Celsius"
    MAX-ACCESS  read-write
    STATUS      current
    DESCRIPTION "Low temperature limit (register 40028, key lo_temp). Raw value in tenths of a unit;
            valid range 50 to 200. The raw value 49 switches the function off. Writable only
            while the unit is stopped. A SET is checked like a web write (device online with
            fresh data, range, run interlock) and then written to the device and read back: a
            rejection by the gateway or the device answers an error (commitFailed for a single
            varbind), an unverified write answers noError and is reported in gwLastWriteResult."
    ::= { mexSetpointEntry 28 }

mexSpHiHum OBJECT-TYPE
    SYNTAX      GwTenths (599..900)
    UNITS       "percent"
    MAX-ACCESS  read-write
    STATUS      current
    DESCRIPTION "High humidity limit (register 40029, key hi_hum). Raw value in tenths of a unit;
            valid range 600 to 900. The raw value 599 switches the function off. Writable only
            while the unit is stopped. A SET is checked like a web write (device online with
            fresh data, range, run interlock) and then written to the device and read back: a
            rejection by the gateway or the device answers an error (commitFailed for a single
            varbind), an unverified write answers noError and is reported in gwLastWriteResult."
    ::= { mexSetpointEntry 29 }

mexSpLoHum OBJECT-TYPE
    SYNTAX      GwTenths (99..400)
    UNITS       "percent"
    MAX-ACCESS  read-write
    STATUS      current
    DESCRIPTION "Low humidity limit (register 40030, key lo_hum). Raw value in tenths of a unit;
            valid range 100 to 400. The raw value 99 switches the function off. Writable only
            while the unit is stopped. A SET is checked like a web write (device online with
            fresh data, range, run interlock) and then written to the device and read back: a
            rejection by the gateway or the device answers an error (commitFailed for a single
            varbind), an unverified write answers noError and is reported in gwLastWriteResult."
    ::= { mexSetpointEntry 30 }

-- ---------------------------------------------------------------- mexRegisters

mexRegTable OBJECT-TYPE
    SYNTAX      SEQUENCE OF MexRegEntry
    MAX-ACCESS  not-accessible
    STATUS      current
    DESCRIPTION "Every mapped holding register of every configured device (read-only, generic
            extension point for other controller types)."
    ::= { mexRegisters 1 }

mexRegEntry OBJECT-TYPE
    SYNTAX      MexRegEntry
    MAX-ACCESS  not-accessible
    STATUS      current
    DESCRIPTION "One register of one device."
    INDEX       { gwDevIndex, mexRegAddr }
    ::= { mexRegTable 1 }

MexRegEntry ::= SEQUENCE {
    mexRegAddr     Integer32,
    mexRegKey      DisplayString,
    mexRegName     GwUtf8String,
    mexRegRaw      Integer32,
    mexRegValue    DisplayString,
    mexRegScale    Integer32,
    mexRegUnit     GwUtf8String,
    mexRegWritable TruthValue,
    mexRegValid    TruthValue
}

mexRegAddr OBJECT-TYPE
    SYNTAX      Integer32 (40001..40059)
    MAX-ACCESS  not-accessible
    STATUS      current
    DESCRIPTION "Register address (4xxxx)."
    ::= { mexRegEntry 1 }

mexRegKey OBJECT-TYPE
    SYNTAX      DisplayString (SIZE (1..32))
    MAX-ACCESS  read-only
    STATUS      current
    DESCRIPTION "Stable register key (for example set_temp)."
    ::= { mexRegEntry 2 }

mexRegName OBJECT-TYPE
    SYNTAX      GwUtf8String (SIZE (0..63))
    MAX-ACCESS  read-only
    STATUS      current
    DESCRIPTION "English register name."
    ::= { mexRegEntry 3 }

mexRegRaw OBJECT-TYPE
    SYNTAX      Integer32 (-32768..65535)
    MAX-ACCESS  read-only
    STATUS      current
    DESCRIPTION "Decoded register value at register scale: sign-extended for signed registers,
            otherwise the full 16-bit word (also for 40005 and bit-field registers)."
    ::= { mexRegEntry 4 }

mexRegValue OBJECT-TYPE
    SYNTAX      DisplayString (SIZE (0..16))
    MAX-ACCESS  read-only
    STATUS      current
    DESCRIPTION "Register value as a decimal number (raw divided by the scale), for example 23.5."
    ::= { mexRegEntry 5 }

mexRegScale OBJECT-TYPE
    SYNTAX      Integer32 (1..100)
    MAX-ACCESS  read-only
    STATUS      current
    DESCRIPTION "Divisor of the raw value (1 or 10)."
    ::= { mexRegEntry 6 }

mexRegUnit OBJECT-TYPE
    SYNTAX      GwUtf8String (SIZE (0..8))
    MAX-ACCESS  read-only
    STATUS      current
    DESCRIPTION "Display unit (UTF-8), empty if none."
    ::= { mexRegEntry 7 }

mexRegWritable OBJECT-TYPE
    SYNTAX      TruthValue
    MAX-ACCESS  read-only
    STATUS      current
    DESCRIPTION "true(1) if the register is writable (through the web API, and through
            mexSetpointTable when it is listed there)."
    ::= { mexRegEntry 8 }

mexRegValid OBJECT-TYPE
    SYNTAX      TruthValue
    MAX-ACCESS  read-only
    STATUS      current
    DESCRIPTION "true(1) if the value was read from the device: device online with fresh data and,
            for the slowly polled limit and option registers, read at least once since it came
            online."
    ::= { mexRegEntry 9 }

-- ---------------------------------------------------------------- gwAlarms

gwAlarmActiveTable OBJECT-TYPE
    SYNTAX      SEQUENCE OF GwAlarmActiveEntry
    MAX-ACCESS  not-accessible
    STATUS      current
    DESCRIPTION "Active alarms."
    ::= { gwAlarms 1 }

gwAlarmActiveEntry OBJECT-TYPE
    SYNTAX      GwAlarmActiveEntry
    MAX-ACCESS  not-accessible
    STATUS      current
    DESCRIPTION "One active alarm of one device."
    INDEX       { gwDevIndex, gwAlarmActiveCode }
    ::= { gwAlarmActiveTable 1 }

GwAlarmActiveEntry ::= SEQUENCE {
    gwAlarmActiveCode     GwAlarmCode,
    gwAlarmActiveName     GwUtf8String,
    gwAlarmActiveSeverity GwAlarmSeverity,
    gwAlarmActiveSince    DateAndTime,
    gwAlarmActiveAcked    TruthValue,
    gwAlarmActiveAckedBy  GwUtf8String,
    gwAlarmActiveValue    Integer32
}

gwAlarmActiveCode OBJECT-TYPE
    SYNTAX      GwAlarmCode
    MAX-ACCESS  not-accessible
    STATUS      current
    DESCRIPTION "Alarm code."
    ::= { gwAlarmActiveEntry 1 }

gwAlarmActiveName OBJECT-TYPE
    SYNTAX      GwUtf8String (SIZE (0..63))
    MAX-ACCESS  read-only
    STATUS      current
    DESCRIPTION "Alarm name (English)."
    ::= { gwAlarmActiveEntry 2 }

gwAlarmActiveSeverity OBJECT-TYPE
    SYNTAX      GwAlarmSeverity
    MAX-ACCESS  read-only
    STATUS      current
    DESCRIPTION "Effective severity."
    ::= { gwAlarmActiveEntry 3 }

gwAlarmActiveSince OBJECT-TYPE
    SYNTAX      DateAndTime
    MAX-ACCESS  read-only
    STATUS      current
    DESCRIPTION "Time the alarm was raised."
    ::= { gwAlarmActiveEntry 4 }

gwAlarmActiveAcked OBJECT-TYPE
    SYNTAX      TruthValue
    MAX-ACCESS  read-only
    STATUS      current
    DESCRIPTION "true(1) if the alarm has been acknowledged."
    ::= { gwAlarmActiveEntry 5 }

gwAlarmActiveAckedBy OBJECT-TYPE
    SYNTAX      GwUtf8String (SIZE (0..11))
    MAX-ACCESS  read-only
    STATUS      current
    DESCRIPTION "Who acknowledged the alarm (empty if not acknowledged): the web account name for
            SNMPv3 requests, web for SNMPv1/v2c requests."
    ::= { gwAlarmActiveEntry 6 }

gwAlarmActiveValue OBJECT-TYPE
    SYNTAX      Integer32
    MAX-ACCESS  read-only
    STATUS      current
    DESCRIPTION "Raw value of the related register when the alarm was raised (1 for pure bit alarms)."
    ::= { gwAlarmActiveEntry 7 }

gwAlarmActiveCount OBJECT-TYPE
    SYNTAX      Gauge32
    MAX-ACCESS  read-only
    STATUS      current
    DESCRIPTION "Number of active alarms."
    ::= { gwAlarms 2 }

gwAlarmCriticalCount OBJECT-TYPE
    SYNTAX      Gauge32
    MAX-ACCESS  read-only
    STATUS      current
    DESCRIPTION "Number of active critical alarms."
    ::= { gwAlarms 3 }

gwAlarmMajorCount OBJECT-TYPE
    SYNTAX      Gauge32
    MAX-ACCESS  read-only
    STATUS      current
    DESCRIPTION "Number of active major alarms."
    ::= { gwAlarms 4 }

gwAlarmMinorCount OBJECT-TYPE
    SYNTAX      Gauge32
    MAX-ACCESS  read-only
    STATUS      current
    DESCRIPTION "Number of active minor alarms."
    ::= { gwAlarms 5 }

gwAlarmInfoCount OBJECT-TYPE
    SYNTAX      Gauge32
    MAX-ACCESS  read-only
    STATUS      current
    DESCRIPTION "Number of active informational alarms."
    ::= { gwAlarms 6 }

gwAlarmEventTable OBJECT-TYPE
    SYNTAX      SEQUENCE OF GwAlarmEventEntry
    MAX-ACCESS  not-accessible
    STATUS      current
    DESCRIPTION "The 32 most recent alarm transitions (raise, clear, acknowledge), oldest first."
    ::= { gwAlarms 7 }

gwAlarmEventEntry OBJECT-TYPE
    SYNTAX      GwAlarmEventEntry
    MAX-ACCESS  not-accessible
    STATUS      current
    DESCRIPTION "One alarm transition."
    INDEX       { gwAlarmEventSeq }
    ::= { gwAlarmEventTable 1 }

GwAlarmEventEntry ::= SEQUENCE {
    gwAlarmEventSeq      Unsigned32,
    gwAlarmEventTime     DateAndTime,
    gwAlarmEventType     INTEGER,
    gwAlarmEventDevIndex GwDevIndex,
    gwAlarmEventCode     GwAlarmCode,
    gwAlarmEventSeverity GwAlarmSeverity,
    gwAlarmEventValue    Integer32,
    gwAlarmEventUser     GwUtf8String
}

gwAlarmEventSeq OBJECT-TYPE
    SYNTAX      Unsigned32 (1..4294967295)
    MAX-ACCESS  not-accessible
    STATUS      current
    DESCRIPTION "Event log sequence number of the transition."
    ::= { gwAlarmEventEntry 1 }

gwAlarmEventTime OBJECT-TYPE
    SYNTAX      DateAndTime
    MAX-ACCESS  read-only
    STATUS      current
    DESCRIPTION "Time of the transition."
    ::= { gwAlarmEventEntry 2 }

gwAlarmEventType OBJECT-TYPE
    SYNTAX      INTEGER { raise(1), clear(2), ack(3) }
    MAX-ACCESS  read-only
    STATUS      current
    DESCRIPTION "Kind of transition."
    ::= { gwAlarmEventEntry 3 }

gwAlarmEventDevIndex OBJECT-TYPE
    SYNTAX      GwDevIndex
    MAX-ACCESS  read-only
    STATUS      current
    DESCRIPTION "Device index."
    ::= { gwAlarmEventEntry 4 }

gwAlarmEventCode OBJECT-TYPE
    SYNTAX      GwAlarmCode
    MAX-ACCESS  read-only
    STATUS      current
    DESCRIPTION "Alarm code."
    ::= { gwAlarmEventEntry 5 }

gwAlarmEventSeverity OBJECT-TYPE
    SYNTAX      GwAlarmSeverity
    MAX-ACCESS  read-only
    STATUS      current
    DESCRIPTION "Severity at the transition."
    ::= { gwAlarmEventEntry 6 }

gwAlarmEventValue OBJECT-TYPE
    SYNTAX      Integer32
    MAX-ACCESS  read-only
    STATUS      current
    DESCRIPTION "Raw value of the related register."
    ::= { gwAlarmEventEntry 7 }

gwAlarmEventUser OBJECT-TYPE
    SYNTAX      GwUtf8String (SIZE (0..11))
    MAX-ACCESS  read-only
    STATUS      current
    DESCRIPTION "Acknowledging user for ack(3) events, otherwise empty: the web account name for
            SNMPv3 requests, web for SNMPv1/v2c requests."
    ::= { gwAlarmEventEntry 8 }

gwAlarmNotifObjects OBJECT IDENTIFIER ::= { gwAlarms 8 }

gwAlarmDevIndex OBJECT-TYPE
    SYNTAX      GwDevIndex
    MAX-ACCESS  accessible-for-notify
    STATUS      current
    DESCRIPTION "Device index of the alarm."
    ::= { gwAlarmNotifObjects 1 }

gwAlarmCode OBJECT-TYPE
    SYNTAX      GwAlarmCode
    MAX-ACCESS  accessible-for-notify
    STATUS      current
    DESCRIPTION "Alarm code."
    ::= { gwAlarmNotifObjects 2 }

gwAlarmName OBJECT-TYPE
    SYNTAX      GwUtf8String (SIZE (0..63))
    MAX-ACCESS  accessible-for-notify
    STATUS      current
    DESCRIPTION "Alarm name (English; for user rules the configured rule name if set)."
    ::= { gwAlarmNotifObjects 3 }

gwAlarmSeverity OBJECT-TYPE
    SYNTAX      GwAlarmSeverity
    MAX-ACCESS  accessible-for-notify
    STATUS      current
    DESCRIPTION "Effective severity."
    ::= { gwAlarmNotifObjects 4 }

gwAlarmTime OBJECT-TYPE
    SYNTAX      DateAndTime
    MAX-ACCESS  accessible-for-notify
    STATUS      current
    DESCRIPTION "Time of the event."
    ::= { gwAlarmNotifObjects 5 }

gwAlarmValue OBJECT-TYPE
    SYNTAX      Integer32
    MAX-ACCESS  accessible-for-notify
    STATUS      current
    DESCRIPTION "Raw value of the related register."
    ::= { gwAlarmNotifObjects 6 }

gwAlarmSeq OBJECT-TYPE
    SYNTAX      Unsigned32
    MAX-ACCESS  accessible-for-notify
    STATUS      current
    DESCRIPTION "Event log sequence number (matches gwAlarmEventSeq)."
    ::= { gwAlarmNotifObjects 7 }

-- ---------------------------------------------------------------- gwComm

gwCommTable OBJECT-TYPE
    SYNTAX      SEQUENCE OF GwCommEntry
    MAX-ACCESS  not-accessible
    STATUS      current
    DESCRIPTION "Modbus communication statistics per configured device. The counters of this table
            can be reset by an administrator (web API); a management application must treat a
            decrease as a discontinuity."
    ::= { gwComm 1 }

gwCommEntry OBJECT-TYPE
    SYNTAX      GwCommEntry
    MAX-ACCESS  not-accessible
    STATUS      current
    DESCRIPTION "Statistics of one device."
    INDEX       { gwDevIndex }
    ::= { gwCommTable 1 }

GwCommEntry ::= SEQUENCE {
    gwCommTx           Counter32,
    gwCommRxOk         Counter32,
    gwCommCrcErrors    Counter32,
    gwCommTimeouts     Counter32,
    gwCommExceptions   Counter32,
    gwCommMalformed    Counter32,
    gwCommOfflineCount Counter32,
    gwCommRttLast      Gauge32,
    gwCommRttAvg       Gauge32,
    gwCommRttMax       Gauge32,
    gwCommCycles       Counter32,
    gwCommOnlineSince  DateAndTime
}

gwCommTx OBJECT-TYPE
    SYNTAX      Counter32
    MAX-ACCESS  read-only
    STATUS      current
    DESCRIPTION "Modbus requests sent."
    ::= { gwCommEntry 1 }

gwCommRxOk OBJECT-TYPE
    SYNTAX      Counter32
    MAX-ACCESS  read-only
    STATUS      current
    DESCRIPTION "Valid responses received."
    ::= { gwCommEntry 2 }

gwCommCrcErrors OBJECT-TYPE
    SYNTAX      Counter32
    MAX-ACCESS  read-only
    STATUS      current
    DESCRIPTION "Responses with a CRC error."
    ::= { gwCommEntry 3 }

gwCommTimeouts OBJECT-TYPE
    SYNTAX      Counter32
    MAX-ACCESS  read-only
    STATUS      current
    DESCRIPTION "Requests without a response in time."
    ::= { gwCommEntry 4 }

gwCommExceptions OBJECT-TYPE
    SYNTAX      Counter32
    MAX-ACCESS  read-only
    STATUS      current
    DESCRIPTION "Modbus exception responses."
    ::= { gwCommEntry 5 }

gwCommMalformed OBJECT-TYPE
    SYNTAX      Counter32
    MAX-ACCESS  read-only
    STATUS      current
    DESCRIPTION "Malformed responses."
    ::= { gwCommEntry 6 }

gwCommOfflineCount OBJECT-TYPE
    SYNTAX      Counter32
    MAX-ACCESS  read-only
    STATUS      current
    DESCRIPTION "Transitions to offline."
    ::= { gwCommEntry 7 }

gwCommRttLast OBJECT-TYPE
    SYNTAX      Gauge32
    UNITS       "milliseconds"
    MAX-ACCESS  read-only
    STATUS      current
    DESCRIPTION "Round-trip time of the last transaction."
    ::= { gwCommEntry 8 }

gwCommRttAvg OBJECT-TYPE
    SYNTAX      Gauge32
    UNITS       "milliseconds"
    MAX-ACCESS  read-only
    STATUS      current
    DESCRIPTION "Average round-trip time (EWMA 1/8)."
    ::= { gwCommEntry 9 }

gwCommRttMax OBJECT-TYPE
    SYNTAX      Gauge32
    UNITS       "milliseconds"
    MAX-ACCESS  read-only
    STATUS      current
    DESCRIPTION "Maximum round-trip time."
    ::= { gwCommEntry 10 }

gwCommCycles OBJECT-TYPE
    SYNTAX      Counter32
    MAX-ACCESS  read-only
    STATUS      current
    DESCRIPTION "Successful poll cycles."
    ::= { gwCommEntry 11 }

gwCommOnlineSince OBJECT-TYPE
    SYNTAX      DateAndTime
    MAX-ACCESS  read-only
    STATUS      current
    DESCRIPTION "Time of the last offline to online transition (1970-01-01 if none)."
    ::= { gwCommEntry 12 }

-- ---------------------------------------------------------------- notifications

gwAlarmRaised NOTIFICATION-TYPE
    OBJECTS     { gwAlarmDevIndex, gwAlarmCode, gwAlarmName, gwAlarmSeverity, gwAlarmTime, gwAlarmValue, gwAlarmSeq }
    STATUS      current
    DESCRIPTION "An alarm was raised."
    ::= { gwNotifications 1 }

gwAlarmCleared NOTIFICATION-TYPE
    OBJECTS     { gwAlarmDevIndex, gwAlarmCode, gwAlarmName, gwAlarmSeverity, gwAlarmTime, gwAlarmValue, gwAlarmSeq }
    STATUS      current
    DESCRIPTION "An alarm was cleared."
    ::= { gwNotifications 2 }

gwCommLost NOTIFICATION-TYPE
    OBJECTS     { gwDevName, gwDevOnline, gwAlarmTime }
    STATUS      current
    DESCRIPTION "Communication with a device was lost. Transitions are coalesced: at most one
            notification per device every 10 seconds, reporting the latest state."
    ::= { gwNotifications 3 }

gwCommRestored NOTIFICATION-TYPE
    OBJECTS     { gwDevName, gwDevOnline, gwAlarmTime }
    STATUS      current
    DESCRIPTION "Communication with a device was restored (coalesced like gwCommLost)."
    ::= { gwNotifications 4 }

gwConfigChanged NOTIFICATION-TYPE
    OBJECTS     { gwLastConfigSection, gwConfigRev }
    STATUS      current
    DESCRIPTION "A configuration section was changed."
    ::= { gwNotifications 5 }

gwFirmwareUpdated NOTIFICATION-TYPE
    OBJECTS     { gwFwVersion }
    STATUS      current
    DESCRIPTION "A new firmware image passed its health check after an update and was marked valid."
    ::= { gwNotifications 6 }

gwTestNotification NOTIFICATION-TYPE
    OBJECTS     { gwFwVersion }
    STATUS      current
    DESCRIPTION "Test notification requested by an administrator."
    ::= { gwNotifications 7 }

-- ---------------------------------------------------------------- conformance

gwCompliances OBJECT IDENTIFIER ::= { gwConformance 1 }
gwGroups      OBJECT IDENTIFIER ::= { gwConformance 2 }

gwCompliance MODULE-COMPLIANCE
    STATUS      current
    DESCRIPTION "Requirements for a MESTIO Gateway agent."
    MODULE      -- this module
        MANDATORY-GROUPS { gwInfoGroup,
                           gwDeviceGroup,
                           mexStatusGroup,
                           mexSetpointGroup,
                           mexRegisterGroup,
                           gwAlarmGroup,
                           gwCommGroup,
                           gwNotifObjectsGroup,
                           gwNotificationsGroup }
    ::= { gwCompliances 1 }

gwInfoGroup OBJECT-GROUP
    OBJECTS     { gwFwVersion,
                  gwMacAddress,
                  gwUptime,
                  gwTimeValid,
                  gwWallTime,
                  gwActiveAlarms,
                  gwConfigRev,
                  gwLastConfigSection,
                  gwLastWriteResult,
                  gwLastWriteDevIndex,
                  gwLastWriteRegAddr,
                  gwLastWriteValue,
                  gwLastWriteReason,
                  gwLastWriteTime,
                  gwLastWriteCommand,
                  gwLastWritePrincipal,
                  gwTrapsSent,
                  gwTrapsDropped,
                  gwInformsFailed }
    STATUS      current
    DESCRIPTION "Gateway information and write results."
    ::= { gwGroups 1 }

gwDeviceGroup OBJECT-GROUP
    OBJECTS     { gwDevName,
                  gwDevSlave,
                  gwDevEnabled,
                  gwDevOnline,
                  gwDevDataAge,
                  gwDevSeq,
                  gwDevCount }
    STATUS      current
    DESCRIPTION "Configured devices."
    ::= { gwGroups 2 }

mexStatusGroup OBJECT-GROUP
    OBJECTS     { mexStatusValid,
                  mexTemperature,
                  mexHumidity,
                  mexCurrent,
                  mexRunState,
                  mexDelayRemaining,
                  mexModeFlags,
                  mexStagesCool,
                  mexStagesHeat,
                  mexStagesHum,
                  mexStagesDehum,
                  mexBlower,
                  mexCoils,
                  mexInputPort,
                  mexAlarmDetail1,
                  mexAlarmDetail2,
                  mexCoolProp,
                  mexHeatProp,
                  mexHumProp }
    STATUS      current
    DESCRIPTION "MEX150 live status."
    ::= { gwGroups 3 }

mexSetpointGroup OBJECT-GROUP
    OBJECTS     { mexSpSetTemp,
                  mexSpSetHum,
                  mexSpCoolDev,
                  mexSpHeatDev,
                  mexSpHumDev,
                  mexSpDehumDev,
                  mexSpRunDelay,
                  mexSpStopDelay,
                  mexSpHiTemp,
                  mexSpLoTemp,
                  mexSpHiHum,
                  mexSpLoHum }
    STATUS      current
    DESCRIPTION "MEX150 writable set points."
    ::= { gwGroups 4 }

mexRegisterGroup OBJECT-GROUP
    OBJECTS     { mexRegKey,
                  mexRegName,
                  mexRegRaw,
                  mexRegValue,
                  mexRegScale,
                  mexRegUnit,
                  mexRegWritable,
                  mexRegValid }
    STATUS      current
    DESCRIPTION "Generic register table."
    ::= { gwGroups 5 }

gwAlarmGroup OBJECT-GROUP
    OBJECTS     { gwAlarmActiveName,
                  gwAlarmActiveSeverity,
                  gwAlarmActiveSince,
                  gwAlarmActiveAcked,
                  gwAlarmActiveAckedBy,
                  gwAlarmActiveValue,
                  gwAlarmActiveCount,
                  gwAlarmCriticalCount,
                  gwAlarmMajorCount,
                  gwAlarmMinorCount,
                  gwAlarmInfoCount,
                  gwAlarmEventTime,
                  gwAlarmEventType,
                  gwAlarmEventDevIndex,
                  gwAlarmEventCode,
                  gwAlarmEventSeverity,
                  gwAlarmEventValue,
                  gwAlarmEventUser }
    STATUS      current
    DESCRIPTION "Alarm tables and counters."
    ::= { gwGroups 6 }

gwCommGroup OBJECT-GROUP
    OBJECTS     { gwCommTx,
                  gwCommRxOk,
                  gwCommCrcErrors,
                  gwCommTimeouts,
                  gwCommExceptions,
                  gwCommMalformed,
                  gwCommOfflineCount,
                  gwCommRttLast,
                  gwCommRttAvg,
                  gwCommRttMax,
                  gwCommCycles,
                  gwCommOnlineSince }
    STATUS      current
    DESCRIPTION "Communication statistics."
    ::= { gwGroups 7 }

gwNotifObjectsGroup OBJECT-GROUP
    OBJECTS     { gwAlarmDevIndex,
                  gwAlarmCode,
                  gwAlarmName,
                  gwAlarmSeverity,
                  gwAlarmTime,
                  gwAlarmValue,
                  gwAlarmSeq }
    STATUS      current
    DESCRIPTION "Objects carried by notifications."
    ::= { gwGroups 8 }

gwNotificationsGroup NOTIFICATION-GROUP
    NOTIFICATIONS { gwAlarmRaised,
                    gwAlarmCleared,
                    gwCommLost,
                    gwCommRestored,
                    gwConfigChanged,
                    gwFirmwareUpdated,
                    gwTestNotification }
    STATUS      current
    DESCRIPTION "Notifications sent by the gateway."
    ::= { gwGroups 9 }

END
